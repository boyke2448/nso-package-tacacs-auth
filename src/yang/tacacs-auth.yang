module tacacs-auth {

  namespace "http://learning.cisco.com/tacacs-auth";
  prefix tacacs-auth;
  yang-version 1.1;

  import ietf-inet-types {
    prefix inet;
  }
  import tailf-common {
    prefix tailf;
  }
  import tailf-ncs {
    prefix ncs;
  }

  description
    "External Auth with TACACS configuration details";

  revision 2021-08-03 {
    description
      "Initial revision.";
  }

  container tacacs-auth {

    // uses ncs:service-data;
    // ncs:servicepoint tacacs-auth-servicepoint;

    // TODO : Convert to list of hosts to enable storing other values in additon to IP address
    // TODO : Support non-standard ports for a host 
    // TODO : Support overriding the global secret
    leaf-list host {
        tailf:info "The IP address for a TACACS host to query";
        type inet:ipv4-address;
        ordered-by user;
    }

    // The secret should be encrypted. AES is currently 2023-10-16 the most populare symetric encryption algorithm supported by NSO
    leaf secret { 
        tailf:info "The TACACS shared-secret to use when communicating with hosts";
        // type string; // Plain text, don't do it man!
        // tailf:des3-cbc-encrypted-string; // You could do this, but why.
        // tailf:aes-cfb-128-encrypted-string; // Better
        tailf:aes-256-cfb-128-encrypted-string; // this is even better.
    }
  }
}
